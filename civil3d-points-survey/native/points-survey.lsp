;;; CDCRD-Digital / Points + Survey v0.1.0 / Civil 3D 2027, COM 13.9
;;; COM writes are not transactional. Failed runs require an audit, never a blind retry.
(vl-load-com)
(defun cdr:q (s) (vl-prin1-to-string s))
(defun cdr:path (s) (strcase (vl-string-translate "\\" "/" s)))
(defun cdr:fail (s) (setq cdr:last-error s) (quit))
(defun cdr:csv (s / out c)
  (setq out "\"")
  (foreach c (vl-string->list s) (setq out (strcat out (if (= c 34) "\"\"" (chr c)))))
  (strcat out "\""))
(defun cdr:row (f n e north z desc)
  (write-line (strcat (itoa n) "," (rtos e 2 12) "," (rtos north 2 12) "," (rtos z 2 12) "," (cdr:csv desc)) f))
(defun cdr:audit (doc output / points p f g first nums)
  (setq points (vlax-get-property doc 'Points))
  (setq f (open (strcat output ".csv") "w" "utf8"))
  (if (not f) (cdr:fail "Cannot open audit CSV"))
  (write-line "number,easting,northing,elevation,description" f)
  (vlax-for p points
    (cdr:row f (vlax-get-property p 'Number) (vlax-get-property p 'Easting)
      (vlax-get-property p 'Northing) (vlax-get-property p 'Elevation) (vlax-get-property p 'RawDescription)))
  (close f)
  (setq f (open (strcat output ".groups.json") "w" "utf8") first T)
  (if (not f) (cdr:fail "Cannot open groups export"))
  (write-line "[" f)
  (vlax-for g (vlax-get-property doc 'PointGroups)
    (setq nums "")
    (vlax-for p points
      (if (= :vlax-true (vlax-invoke-method g 'ContainsPoint (vlax-get-property p 'Number)))
        (setq nums (strcat nums (if (= nums "") "" ",") (itoa (vlax-get-property p 'Number))))))
    (write-line (strcat (if first "" ",") "{\"name\":" (cdr:q (vlax-get-property g 'Name))
      ",\"count\":" (itoa (vlax-get-property g 'PointCount)) ",\"numbers\":[" nums "]}") f)
    (setq first nil))
  (write-line "]" f) (close f))
(defun cdr:assert-points (points rows / r p)
  (foreach r rows
    (setq p (vlax-invoke-method points 'Find (car r)))
    (if (or (> (abs (- (vlax-get-property p 'Easting) (nth 1 r))) 1e-7)
            (> (abs (- (vlax-get-property p 'Northing) (nth 2 r))) 1e-7)
            (> (abs (- (vlax-get-property p 'Elevation) (nth 3 r))) 1e-7)
            (/= (vlax-get-property p 'RawDescription) (nth 4 r)))
      (cdr:fail "COGO reread mismatch"))))
(defun cdr:group (doc name rows / groups g q nums r)
  (setq groups (vlax-get-property doc 'PointGroups))
  (vlax-for g groups (if (= (strcase name) (strcase (vlax-get-property g 'Name))) (cdr:fail "Group already exists")))
  (cdr:assert-points (vlax-get-property doc 'Points) rows)
  (setq nums "")
  (foreach r rows (setq nums (strcat nums (if (= nums "") "" ",") (itoa (car r)))))
  (setq g (vlax-invoke-method groups 'Add name) q (vlax-get-property g 'QueryBuilder))
  (vlax-invoke-method q 'Clear)
  (vlax-put-property q 'IncludeNumbers nums)
  (vlax-invoke-method g 'Update)
  (if (/= (vlax-get-property g 'PointCount) (length rows)) (cdr:fail "Group count mismatch"))
  (foreach r rows (if (= :vlax-false (vlax-invoke-method g 'ContainsPoint (car r))) (cdr:fail "Group membership mismatch")))
  (length rows))
(defun cdr:import (doc rows / points r p)
  (setq points (vlax-get-property doc 'Points))
  (if (/= 0 (vlax-get-property points 'Count)) (cdr:fail "Import requires an empty disposable drawing"))
  (foreach r rows
    (setq p (vlax-invoke-method points 'Add (vlax-3d-point (list (nth 1 r) (nth 2 r) (nth 3 r)))))
    (vlax-put-property p 'Number (car r))
    (vlax-put-property p 'RawDescription (nth 4 r)))
  (cdr:assert-points points rows)
  (if (/= (vlax-get-property points 'Count) (length rows)) (cdr:fail "Imported count mismatch"))
  (length rows))
(defun cdr:array-list (value / a)
  (setq a (if (= (type value) 'VARIANT) (vlax-variant-value value) value))
  (cond ((null a) nil)
        ((= (type a) 'SAFEARRAY) (if (< (vlax-safearray-get-u-bound a 1) 0) nil (vlax-safearray->list a)))
        ((listp a) a)
        (T (cdr:fail "Unexpected Survey point-number array"))))
(defun cdr:survey (action folder name zone rows output / app projects prior project settings nets net nc r p f res cleanup err)
  (setq app (vla-GetInterfaceObject (vlax-get-acad-object) "AeccXUiSurvey.AeccSurveyApplication.13.9")
        projects (vlax-get-property (vla-get-ActiveDocument app) 'Projects)
        prior (vlax-invoke-method projects 'GetWorkingFolder))
  (setq f (open (strcat output ".state.json") "w" "utf8"))
  (if (not f) (cdr:fail "Cannot write recovery checkpoint"))
  (write-line (strcat "{\"prior_working_folder\":" (cdr:q prior) ",\"database\":" (cdr:q name) "}") f)
  (close f) (setq f nil)
  (setq res (vl-catch-all-apply '(lambda ()
    (if (not (vl-file-directory-p (strcat folder "/" name))) (cdr:fail "Create a new empty Survey database first"))
    (vlax-invoke-method projects 'SetWorkingFolder folder)
    (setq project (vlax-invoke-method projects 'FindItem name))
    (vlax-invoke-method project 'Open)
    (setq settings (vlax-invoke-method project 'GetProjectSettings))
    (if (= action "survey-import")
      (progn
        (if (or (/= 0 (vlax-get-property (vlax-get-property project 'Networks) 'Count))
                (/= 0 (vlax-get-property (vlax-get-property project 'Figures) 'Count))
                (cdr:array-list (vlax-invoke-method project 'GetPointNumbers)))
          (cdr:fail "Survey import requires an empty database"))
        (vlax-put-property settings 'DistanceUnit 2)
        (vlax-put-property settings 'Zone zone)
        (vlax-invoke-method project 'UpdateProjectSettings settings)
        (setq nets (vlax-get-property project 'Networks))
        (if (/= 0 (vlax-get-property nets 'Count)) (cdr:fail "New Survey DB is not empty"))
        (setq net (vlax-invoke-method nets 'Create "COORDINATES_ONLY"))
        (vlax-put-property net 'Description "Imported coordinates only; no field observations or adjustment.")
        (vlax-invoke-method net 'Save)
        (setq nc (vlax-get-property net 'NonControlPoints))
        (foreach r rows
          (setq p (vlax-invoke-method nc 'Create (car r) (strcat "P" (itoa (car r))) (nth 4 r) (nth 1 r) (nth 2 r) (nth 3 r)))
          (vlax-invoke-method p 'Save))
        (vlax-invoke-method net 'Save)
        (vlax-invoke-method project 'Close)
        (vlax-invoke-method project 'Open)))
    (if (/= (length rows) (length (cdr:array-list (vlax-invoke-method project 'GetPointNumbers))))
      (cdr:fail "Survey point count mismatch"))
    (setq settings (vlax-invoke-method project 'GetProjectSettings))
    (if (or (/= 2 (vlax-get-property settings 'DistanceUnit)) (/= zone (vlax-get-property settings 'Zone))) (cdr:fail "Survey unit/zone mismatch"))
    (setq f (open (strcat output ".csv") "w" "utf8"))
    (if (not f) (cdr:fail "Cannot open Survey CSV"))
    (write-line "number,easting,northing,elevation,description" f)
    (foreach r rows
      (setq p (vlax-invoke-method project 'GetPointByNumber (car r)))
      (if (or (> (abs (- (vlax-get-property p 'Easting) (nth 1 r))) 1e-7)
              (> (abs (- (vlax-get-property p 'Northing) (nth 2 r))) 1e-7)
              (> (abs (- (vlax-get-property p 'Elevation) (nth 3 r))) 1e-7)
              (/= (vlax-get-property p 'Description) (nth 4 r))) (cdr:fail "Survey reread mismatch"))
      (cdr:row f (vlax-get-property p 'Number) (vlax-get-property p 'Easting) (vlax-get-property p 'Northing) (vlax-get-property p 'Elevation) (vlax-get-property p 'Description)))
    (close f) (setq f nil)
    (length rows))))
  (if f (close f))
  (if project (progn (setq cleanup (vl-catch-all-apply 'vlax-invoke-method (list project 'Close)))
    (if (vl-catch-all-error-p cleanup) (setq err (vl-catch-all-error-message cleanup)))))
  (setq cleanup (vl-catch-all-apply 'vlax-invoke-method (list projects 'SetWorkingFolder prior)))
  (if (vl-catch-all-error-p cleanup) (setq err (vl-catch-all-error-message cleanup)))
  (if (/= (cdr:path prior) (cdr:path (vlax-invoke-method projects 'GetWorkingFolder))) (setq err "Working folder restoration failed"))
  (if err (cdr:fail (strcat "Survey cleanup failed: " err)))
  (if (vl-catch-all-error-p res) (cdr:fail (if cdr:last-error cdr:last-error (vl-catch-all-error-message res))))
  res)
(defun cdr:run (action drawing count output name rows folder zone / receipt result app doc points n f err cdr:last-error)
  (setq receipt (strcat output ".json"))
  (if (or (findfile receipt) (findfile (strcat output ".csv"))) (cdr:fail "Output already exists; inspect previous run"))
  (setq f (open receipt "w" "utf8"))
  (if (not f) (cdr:fail "Output folder must exist and be writable"))
  (write-line "{\"ok\":false,\"state\":\"running\",\"warning\":\"Do not repeat; inspect native state if interrupted.\"}" f)
  (close f) (setq f nil)
  (setq result (vl-catch-all-apply '(lambda ()
    (if (/= (cdr:path drawing) (cdr:path (strcat (getvar "DWGPREFIX") (getvar "DWGNAME")))) (cdr:fail "Wrong active drawing"))
    (if (/= 6 (getvar "INSUNITS")) (cdr:fail "Drawing must use metres"))
    (setq app (vla-GetInterfaceObject (vlax-get-acad-object) "AeccXUiLand.AeccApplication.13.9")
          doc (vla-get-ActiveDocument app) points (vlax-get-property doc 'Points))
    (if (/= 2 (vlax-get-property (vlax-get-property (vlax-get-property (vlax-get-property doc 'Settings) 'DrawingSettings) 'UnitZoneSettings) 'DrawingUnits))
      (cdr:fail "Civil drawing units must be metres, not only INSUNITS"))
    (if (/= count (vlax-get-property points 'Count)) (cdr:fail "Unexpected COGO count"))
    (cond
      ((= action "audit") (cdr:audit doc output) (setq n count))
      ((= action "import") (setq n (cdr:import doc rows)) (cdr:audit doc output))
      ((= action "group") (setq n (cdr:group doc name rows)) (cdr:audit doc output))
      ((member action '("survey-import" "survey-read")) (setq n (cdr:survey action folder name zone rows output)))
      (T (cdr:fail "Unknown action")))
    n)))
  (setq err (if (vl-catch-all-error-p result) (if cdr:last-error cdr:last-error (vl-catch-all-error-message result)) ""))
  (setq f (open receipt "w" "utf8"))
  (if (not f) (cdr:fail "Native operation may have completed; receipt failed"))
  (write-line (strcat "{\"version\":\"0.1.0\",\"ok\":" (if (= err "") "true" "false")
    ",\"action\":" (cdr:q action) ",\"count\":" (itoa (if n n 0)) ",\"error\":" (cdr:q err) "}") f)
  (close f) (princ (strcat "\nCDCRD Points/Survey: " (if (= err "") "OK" err))) (princ))
(princ)
